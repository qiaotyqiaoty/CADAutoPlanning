Attribute VB_Name = "Form1"
Attribute VB_Base = "0{448A7513-7258-45A5-B89C-1C89FF05C8D7}{E46BDB6D-E44D-4BF4-B727-2FE77C7E6ED0}"
Attribute VB_GlobalNameSpace = False
Attribute VB_Creatable = False
Attribute VB_PredeclaredId = True
Attribute VB_Exposed = False
Attribute VB_TemplateDerived = False
Attribute VB_Customizable = False
Function ssArray(ss As AcadSelectionSet)
    Dim retVal() As AcadEntity, i As Long
    ReDim retVal(0 To ss.Count - 1)
    For i = 0 To ss.Count - 1
        Set retVal(i) = ss.Item(i)
    Next
    ssArray = retVal
End Function

'返回
Private Sub CmdBack_Click()
    Form1.hide
    Form2.show
End Sub

'选定图块
Private Sub CmdFindBlk_Click()
    Form1.hide
    'define variables
    Dim strname As String
    Dim objSS As AcadSelectionSet
    Dim objBlock As AcadBlock
    Dim objBRef As AcadBlockReference
    Dim objSourceEnts() As Object
    Dim varDestEnts As Variant
    Dim intI As Integer
    Dim dblOrigin(2) As Double
    Dim insertionPt(2) As Double
    Dim bsPt(2) As Double
    Dim pickPt As Variant
    Dim objNew As Object
    Dim currentTime As Date
    
    'initialize
    'ThisDrawing.PurgeAll
    
    'set the user input variable and origin
    currentTime = Now()
    strname = "QP_" & Format(currentTime, "MMDD_HHmmSS")

    
    'Selection set
    On Error Resume Next
        Set objSS = ThisDrawing.SelectionSets.Item("SSet")
    Set objSS = ThisDrawing.SelectionSets.Add("SSet")
    objSS.SelectOnScreen
    
    If objSS.Count = 0 Then GoTo BACK
    
    'Insertion point
    dblOrigin(0) = 0: dblOrigin(1) = 0: dblOrigin(2) = 0
    pickPt = ThisDrawing.Utility.GetPoint(dblOrigin, "Pick base point:")
    
    'put selected entities into an array for CopyObjects
    ReDim objSourceEnts(objSS.Count - 1)
    For intI = 0 To objSS.Count - 1
        Set objSourceEnts(intI) = objSS(intI)
    Next
    Form1.Label17.Caption = "选定图元数：" & str(objSS.Count)
    Form1.Label18.Caption = strname
    
    'create the 'empty' block using the given block name
    Set objBlock = ThisDrawing.Blocks.Add(pickPt, strname)

    'copy selected entities into the block
    varDestEnts = ThisDrawing.CopyObjects(objSourceEnts, objBlock)

    'clear
    objSS.Erase
    ThisDrawing.SelectionSets("SSet").Delete
    
    'show block reference
    Set objBRef = ThisDrawing.ModelSpace.InsertBlock(pickPt, strname, 1, 1, 1, 0)
    objNew = objBRef.Explode
    objBRef.Delete
    
BACK:
    Form1.show
    
End Sub

'清空输入的数据
Private Sub CommandButton1_Click()
    Form1.bSize1.Text = ""
    Form1.bSize2.Text = ""
    Form1.sSize1.Text = ""
    Form1.sSize2.Text = ""
    Form1.Area.Text = ""
    Form1.bsArea.Text = ""
    Form1.Dist1.Text = ""
    Form1.Dist2.Text = ""
    Form1.subnum.Text = ""
End Sub


'默认数据
Private Sub CommandDefault_Click()
    Form1.bSize1.Text = 200
    Form1.bSize2.Text = 200
    Form1.sSize1.Text = 10
    Form1.sSize2.Text = 10
    Form1.Area.Text = 180
    Form1.bsArea.Text = 100
    Form1.Dist1.Text = 6
    Form1.Dist2.Text = 15
    Form1.subnum.Text = 2
End Sub

'开始按键
Private Sub CommandButtonOK_Click()
    'define variables
    Dim objSS As AcadSelectionSet
    Dim objBlock As AcadBlock
    Dim objBRef As AcadBlockReference
    Dim intI As Integer
    Dim dblOrigin(2) As Double
    Dim bsPtCalc(2) As Double
    Dim insertionPt(2) As Double
    Dim bsPt(2) As Double
    Dim pickPt As Variant
    Dim objNew As Object
    Dim p11 As Double, p12 As Double, p21 As Double, p22 As Double
    Dim output() As Double
    Dim x0 As Double, y0 As Double, x1 As Double, y1 As Double, Area As Double, bsArea As Double, distx As Double, disty As Double, subnum As Integer, arrDir As Integer
    Dim PL(0 To 9) As Double
    Dim i As Integer, j As Integer, n As Integer
    Dim strname As String
    
    Form1.hide
    If Form1.subnum.Text = "" Then
        Form1.subnum.Text = 1
    End If
    dblOrigin(0) = 0: dblOrigin(1) = 0: dblOrigin(2) = 0
    
    '数据输入
    If Form1.OptM.Value = True Then
        x0 = Val(Form1.bSize1.Text)
        y0 = Val(Form1.bSize2.Text)
        x1 = Val(Form1.sSize1.Text)
        y1 = Val(Form1.sSize2.Text)
        Area = Val(Form1.Area.Text)
        bsArea = Val(Form1.bsArea.Text)
        distx = Val(Form1.Dist1.Text)
        disty = Val(Form1.Dist2.Text)
        subnum = Int(Val(Form1.subnum.Text))
        strname = Form1.Label18.Caption
    ElseIf Form1.OptMM.Value = True Then
        x0 = Val(Form1.bSize1.Text) * 1000
        y0 = Val(Form1.bSize2.Text) * 1000
        x1 = Val(Form1.sSize1.Text) * 1000
        y1 = Val(Form1.sSize2.Text) * 1000
        Area = Val(Form1.Area.Text) * 1000000
        bsArea = Val(Form1.bsArea.Text) * 1000000
        distx = Val(Form1.Dist1.Text) * 1000
        disty = Val(Form1.Dist2.Text) * 1000
        subnum = Int(Val(Form1.subnum.Text))
        strname = Form1.Label18.Caption
    End If

        '选点
        On Error Resume Next
        pickPt = ThisDrawing.Utility.GetPoint(dblOrigin, "Pick base point for array:")
        If err Then pickPt = dblOrigin
        
        '读取块
        Set objBlock = ThisDrawing.Blocks.Item(strname)
        
        '画出矩形
        p11 = pickPt(0)
        p12 = pickPt(1)
        'On Error GoTo ESC01
        p21 = pickPt(0) + x0
        p22 = pickPt(1) + y0
        
        PL(0) = p11: PL(1) = p12
        PL(2) = p21: PL(3) = p12
        PL(4) = p21: PL(5) = p22
        PL(6) = p11: PL(7) = p22
        PL(8) = p11: PL(9) = p12
        'On Error GoTo ESC02
        ThisDrawing.ModelSpace.AddLightWeightPolyline (PL)
        
        'Output data
        If Form1.OptLP1.Value = True Then arrDir = 1
        If Form1.OptLP2.Value = True Then arrDir = 2
        If Form1.OptLP3.Value = True Then arrDir = 0
        output = Q_RecArrS(x0, y0, x1, y1, Area, bsArea, distx, disty, subnum, arrDir)
        
        Form1.DebugText.Locked = True
        Form1.DebugText.Text = "强排小程序 v1.0.0 Beta版" & vbCrLf & _
        "日期：" & Format(Now(), "yyyy-MM-dd") & vbCrLf & _
        "时间：" & Format(Now(), "HH:mm:SS") & vbCrLf & _
        "模式：" & "矩形地块-进深方向联排" & vbCrLf & _
        "单个组团户数：" & str(subnum) & vbCrLf & vbCrLf & _
        "计算结果：" & vbCrLf & _
        "总户数：" & str(output(0)) & vbCrLf & _
        "容积率：" & Format(str(output(7)), "0.000") & vbCrLf & _
        "覆盖率：" & Format(str(output(8)), "0.00%") & vbCrLf & _
        "numys" & str(output(3)) & vbCrLf & _
        "numyp" & str(output(4)) & vbCrLf & _
        "numxs" & str(output(1)) & vbCrLf & _
        "numxp" & str(output(2)) & vbCrLf & _
        "rx" & str(output(5)) & vbCrLf & _
        "ry" & str(output(6)) & vbCrLf & _
        "地块基点位置坐标：" & vbCrLf & _
        Format(str(pickPt(0)), "0.0000") & "," & Format(str(pickPt(1)), "0.0000") & "," & Format(str(pickPt(2)), "0.0000") & vbCrLf & _
        "各户基点位置坐标："
        
        '开始绘图
        insertionPt(0) = pickPt(0) + output(5) / 2: insertionPt(2) = 0
        For n = 0 To (CInt(output(1)) - 1)
            insertionPt(1) = pickPt(1) + output(6) / 2
            For i = 0 To (CInt(output(3)) - 1)
                For j = 0 To (subnum - 1)
                    Set objBRef = ThisDrawing.ModelSpace.InsertBlock(insertionPt, strname, 1, 1, 1, 0)
                    objNew = objBRef.Explode
                    objBRef.Erase
                    insertionPt(1) = insertionPt(1) + y1
                    Form1.DebugText.Text = Form1.DebugText.Text + vbCrLf + str(insertionPt(0)) + "," + str(insertionPt(1)) + "," + str(insertionPt(2))
                Next j
                insertionPt(1) = insertionPt(1) + disty
                Form1.DebugText.Text = Form1.DebugText.Text + vbCrLf + str(insertionPt(0)) + "," + str(insertionPt(1)) + "," + str(insertionPt(2))
            Next i
            
            For i = 0 To (CInt(output(4)) - 1)
                Set objBRef = ThisDrawing.ModelSpace.InsertBlock(insertionPt, strname, 1, 1, 1, 0)
                Set objNew = objBRef.Explode
                objBRef.Erase
                insertionPt(1) = insertionPt(1) + y1
                Form1.DebugText.Text = Form1.DebugText.Text + vbCrLf + str(insertionPt(0)) + "," + str(insertionPt(1)) + "," + str(insertionPt(2))
            Next i
            insertionPt(0) = insertionPt(0) + x1 + distx
            Form1.DebugText.Text = Form1.DebugText.Text + vbCrLf + str(insertionPt(0)) + "," + str(insertionPt(1)) + "," + str(insertionPt(2))
        Next n
        
        ThisDrawing.SelectionSets.Item("SSet").Delete
        
        '插入文字
        If Form1.CheckBoxPrint.Value = True Then
        
            Dim mtextObj As AcadMText
            Dim mtextWidth As Double
            Dim mtextString As String
            Dim mtextPt(0 To 2) As Double
            
            mtextWidth = 0.5 * x0
            If Form1.OptM.Value = True Then
                mtextString = _
                "地块尺寸：" & str(x0) & "*" & str(y0) & vbCrLf & _
                "单体尺寸：" & str(x1) & "*" & str(y1) & vbCrLf & _
                "单体建筑面积：" & str(Area) & vbCrLf & _
                "基底面积：" & str(bsArea) & vbCrLf & _
                "总户数：" & str(output(0)) & vbCrLf & _
                "容积率：" & Format(str(output(7)), "0.000") & vbCrLf & _
                "覆盖率：" & Format(str(output(8)), "0.00%")
            Else
                mtextString = _
                "地块尺寸：" & Format(x0 / 1000, "0") & "*" & Format(y0 / 1000, "0") & vbCrLf & _
                "单体尺寸：" & Format(x1 / 1000, "0.0") & "*" & Format(y1 / 1000, "0.0") & vbCrLf & _
                "单体建筑面积：" & Format(Area / 1000000, "0.0") & vbCrLf & _
                "基底面积：" & Format(bsArea / 1000000, "0.0") & vbCrLf & _
                "总户数：" & str(output(0)) & vbCrLf & _
                "容积率：" & Format(str(output(7)), "0.000") & vbCrLf & _
                "覆盖率：" & Format(str(output(8)), "0.00%")
            End If
            mtextPt(0) = pickPt(0) + 1.2 * x0: mtextPt(1) = pickPt(0) + y0: mtextPt(2) = 0
            Set mtextObj = ThisDrawing.ModelSpace.AddMText(insertionPt, mtextWidth, mtextString)

        End If

        GoTo BACK
        

'Quit
ESC01:
    If MsgBox("输入数值不正确！按确认键重新输入", vbOKCancel) = vbOK Then
        GoTo BACK
    Else
        End
    End If
    GoTo BACK
ESC02:
    If MsgBox("错误！", vbOKCancel) = vbOK Then
        GoTo BACK
    Else
        End
    End If
    GoTo BACK
BACK:
    Form1.show
End Sub

'退出
Private Sub CmdQuit_Click()

End

End Sub


'无联排
Private Sub OptLP3_Click()
    If Form1.subnum.Enabled = True Then
        Form1.subnum.BackColor = &H8000000F
        Form1.subnum.Enabled = False
        Form1.subnum.Text = str(1)
    End If
End Sub

'x联排
Private Sub OptLP1_Click()
    If Form1.subnum.Enabled = False Then
        Form1.subnum.BackColor = &H80000005
        Form1.subnum.Enabled = True
    End If
End Sub

'y联排
Private Sub OptLP2_Click()
    If Form1.subnum.Enabled = False Then
        Form1.subnum.BackColor = &H80000005
        Form1.subnum.Enabled = True
    End If
End Sub



'关于
Private Sub CmdAbout_Click()
    Form1.hide
    If MsgBox("QP v1.0 by 小乔 2018.8", vbOKOnly) = vbOK Then
        Form1.show
    Else
        Form1.show
    End If
End Sub

Attribute VB_Name = "Form2"
Attribute VB_Base = "0{EC039AA6-3F29-4170-8340-ED31A7F0AFA6}{0CE7B8F6-3C0F-4318-A0AD-804722CE3ECE}"
Attribute VB_GlobalNameSpace = False
Attribute VB_Creatable = False
Attribute VB_PredeclaredId = True
Attribute VB_Exposed = False
Attribute VB_TemplateDerived = False
Attribute VB_Customizable = False
Private Sub Cmd1_Click()
Form2.hide
If Form2.OptRec.Value = True Then
    Form1.show
ElseIf Form2.OptOth.Value = True Then
    Form4.show
Else
    Form4.show
End If

End Sub

Private Sub Cmd2_Click()
    Form2.hide
    If Form2.OptRec.Value = True Then
        If MsgBox("开发中，敬请期待！", vbOKOnly) = vbOK Then
            Form2.show
        Else
            Form2.show
        End If
    ElseIf Form2.OptOth.Value = True Then
        Form5.show
    Else
        Form4.show
    End If

'Form2.hide
'Form3.show
End Sub

Private Sub CommandButton1_Click()
    Form2.hide
    If MsgBox("QP v1.0 by 小乔 2018.9", vbOKOnly) = vbOK Then
        Form2.show
    Else
        Form2.show
    End If
End Sub

Private Sub CommandButton2_Click()
End

End Sub

Private Sub Label2_Click()

End Sub

Attribute VB_Name = "Form3"
Attribute VB_Base = "0{A8328BEB-DAD2-45BE-A35A-D43924C9618B}{58766AC3-9F35-4377-8211-65D5527F49F8}"
Attribute VB_GlobalNameSpace = False
Attribute VB_Creatable = False
Attribute VB_PredeclaredId = True
Attribute VB_Exposed = False
Attribute VB_TemplateDerived = False
Attribute VB_Customizable = False

Private Sub CmdBack_Click()
    Form3.hide
    Form2.show
End Sub

Private Sub CmdFindBlk_Click()
    Form3.hide
    'define variables
    Dim strname As String
    Dim objSS As AcadSelectionSet
    Dim objBlock As AcadBlock
    Dim objBRef As AcadBlockReference
    Dim objSourceEnts() As Object
    Dim varDestEnts As Variant
    Dim intI As Integer
    Dim dblOrigin(2) As Double
    Dim insertionPt(2) As Double
    Dim bsPt(2) As Double
    Dim pickPt As Variant
    Dim objNew As Object
    Dim currentTime As Date
    
    'initialize
    'ThisDrawing.PurgeAll
    
    'set the user input variable and origin
    currentTime = Now()
    strname = "QP_" & Format(currentTime, "MMDD_HHmmSS")

    
    'Selection set
    On Error Resume Next
        Set objSS = ThisDrawing.SelectionSets.Item("SSet")
    Set objSS = ThisDrawing.SelectionSets.Add("SSet")
    objSS.SelectOnScreen
    
    If objSS.Count = 0 Then GoTo BACK
    
    'Insertion point
    dblOrigin(0) = 0: dblOrigin(1) = 0: dblOrigin(2) = 0
    pickPt = ThisDrawing.Utility.GetPoint(dblOrigin, "Pick base point:")
    
    'put selected entities into an array for CopyObjects
    ReDim objSourceEnts(objSS.Count - 1)
    For intI = 0 To objSS.Count - 1
        Set objSourceEnts(intI) = objSS(intI)
    Next
    Form3.Label17.Caption = "选定图元数：" & str(objSS.Count)
    Form3.Label18.Caption = strname
    
    'create the 'empty' block using the given block name
    Set objBlock = ThisDrawing.Blocks.Add(pickPt, strname)

    'copy selected entities into the block
    varDestEnts = ThisDrawing.CopyObjects(objSourceEnts, objBlock)

    'clear
    objSS.Erase
    ThisDrawing.SelectionSets("SSet").Delete
    
    'show block reference
    Set objBRef = ThisDrawing.ModelSpace.InsertBlock(pickPt, strname, 1, 1, 1, 0)
    objNew = objBRef.Explode
    objBRef.Delete
    
BACK:
    Form3.show
    
End Sub

'导入
Private Sub CmdImport_Click()
    'On Error Resume Next
    Dim xl, xb As Object
    Dim ImportNum As Integer
    Set xl = CreateObject("Excel.Application")
    xl.Visible = False
    'On Error Resume Next
    Set xlbook = xl.Workbooks.Open(ThisDrawing.Path & "\" & Form3.PathFile.Text)
    Set xlsheet = xl.ActiveSheet
    ImportNum = Int(Form3.ImportNum.Text) + 1
    Form3.projName.Text = xlsheet.Cells(1, ImportNum).Value
    Form3.bSize1.Text = xlsheet.Cells(6, ImportNum).Value
    Form3.bSize2.Text = xlsheet.Cells(7, ImportNum).Value
    Form3.sSize1.Text = xlsheet.Cells(2, ImportNum).Value
    Form3.sSize2.Text = xlsheet.Cells(3, ImportNum).Value
    Form3.Area.Text = xlsheet.Cells(4, ImportNum).Value
    Form3.bsArea.Text = xlsheet.Cells(11, ImportNum).Value
    Form3.Dist1.Text = xlsheet.Cells(8, ImportNum).Value
    Form3.Dist2.Text = xlsheet.Cells(9, ImportNum).Value
    xlbook.Close
    xl.Quit
    Set xlsheet = Nothing
    Set xlbook = Nothing
    Set xl = Nothing
End Sub

Private Sub CmdQuit_Click()
End
End Sub

'文件夹中显示
Private Sub CmdShowExp_Click()
    Shell "Explorer " & ThisDrawing.Path, vbNormalFocus
End Sub

Private Sub CommandButtonOK_Click()
    'define variables
    Dim objSS As AcadSelectionSet
    Dim objBlock As AcadBlock
    Dim objBRef As AcadBlockReference
    Dim intI As Integer
    Dim dblOrigin(2) As Double
    Dim bsPtCalc(2) As Double
    Dim insertionPt(2) As Double
    Dim bsPt(2) As Double
    Dim pickPt As Variant
    Dim objNew As Object
    Dim p11 As Double, p12 As Double, p21 As Double, p22 As Double
    Dim output() As Double
    Dim arrDir As Integer
    Dim x0 As Double, y0 As Double, x1 As Double, y1 As Double, Area As Double, bsArea As Double, distx As Double, disty As Double, subnum As Integer
    Dim PL(0 To 9) As Double
    Dim i As Integer, j As Integer, n As Integer
    Dim strname As String
    
    Form3.hide
    If Form3.subnum.Text = "" Then
        Form3.subnum.Text = 1
    End If
    dblOrigin(0) = 0: dblOrigin(1) = 0: dblOrigin(2) = 0
    
    '数据输入
    If Form3.OptM.Value = True Then
        x0 = Val(Form3.bSize1.Text)
        y0 = Val(Form3.bSize2.Text)
        x1 = Val(Form3.sSize1.Text)
        y1 = Val(Form3.sSize2.Text)
        Area = Val(Form3.Area.Text)
        bsArea = Val(Form3.bsArea.Text)
        distx = Val(Form3.Dist1.Text)
        disty = Val(Form3.Dist2.Text)
        subnum = Int(Val(Form3.subnum.Text))
        strname = Form3.Label18.Caption
    ElseIf Form3.OptMM.Value = True Then
        x0 = Val(Form3.bSize1.Text) * 1000
        y0 = Val(Form3.bSize2.Text) * 1000
        x1 = Val(Form3.sSize1.Text) * 1000
        y1 = Val(Form3.sSize2.Text) * 1000
        Area = Val(Form3.Area.Text) * 1000000
        bsArea = Val(Form3.bsArea.Text) * 1000000
        distx = Val(Form3.Dist1.Text) * 1000
        disty = Val(Form3.Dist2.Text) * 1000
        subnum = Int(Val(Form3.subnum.Text))
        strname = Form3.Label18.Caption
    Else
        x0 = Val(Form3.bSize1.Text)
        y0 = Val(Form3.bSize2.Text)
        x1 = Val(Form3.sSize1.Text)
        y1 = Val(Form3.sSize2.Text)
        Area = Val(Form3.Area.Text)
        bsArea = Val(Form3.bsArea.Text)
        distx = Val(Form3.Dist1.Text)
        disty = Val(Form3.Dist2.Text)
        subnum = Int(Val(Form3.subnum.Text))
        strname = Form3.Label18.Caption
    End If
    
    '矩形地块强排条件
        '选点
        Set objBlock = ThisDrawing.Blocks.Item(strname)
        On Error Resume Next
        pickPt = ThisDrawing.Utility.GetPoint(dblOrigin, "Pick base point for array:")
        If err Then pickPt = dblOrigin
        
        '画出矩形
        p11 = pickPt(0)
        p12 = pickPt(1)
        'On Error GoTo ESC01
        p21 = pickPt(0) + x0
        p22 = pickPt(1) + y0
        
        PL(0) = p11: PL(1) = p12
        PL(2) = p21: PL(3) = p12
        PL(4) = p21: PL(5) = p22
        PL(6) = p11: PL(7) = p22
        PL(8) = p11: PL(9) = p12
        'On Error GoTo ESC02
        ThisDrawing.ModelSpace.AddLightWeightPolyline (PL)
        
        'Output data
        If Form3.OptLP1.Value = True Then arrDir = 1
        If Form3.OptLP2.Value = True Then arrDir = 2
        If Form3.OptLP3.Value = True Then arrDir = 0
        output = Q_RecArrS(x0, y0, x1, y1, Area, bsArea, distx, disty, subnum, arrDir)
        Dim sf As Integer
        If arrDir = 1 Then
            sf = 2
            Else
            sf = 1
            End If
        Form3.DebugText.Locked = True
        Form3.DebugText.Text = "强排小程序 v1.0.0 Beta版" & vbCrLf & _
        "日期：" & Format(Now(), "yyyy-MM-dd") & vbCrLf & _
        "时间：" & Format(Now(), "HH:mm:SS") & vbCrLf & _
        "模式：" & "矩形地块-进深方向联排" & vbCrLf & _
        "单个组团户数：" & str(subnum) & vbCrLf & vbCrLf & _
        "计算结果：" & vbCrLf & _
        "总户数：" & str(output(0) * sf) & vbCrLf & _
        "容积率：" & Format(str(output(7) * sf), "0.000") & vbCrLf & _
        "覆盖率：" & Format(str(output(8) * sf), "0.00%") & vbCrLf & _
        "numys" & str(output(3)) & vbCrLf & _
        "numyp" & str(output(4)) & vbCrLf & _
        "numxs" & str(output(1)) & vbCrLf & _
        "numxp" & str(output(2)) & vbCrLf & _
        "rx" & str(output(5)) & vbCrLf & _
        "ry" & str(output(6)) & vbCrLf & _
        "地块基点位置坐标：" & vbCrLf & _
        Format(str(pickPt(0)), "0.0000") & "," & Format(str(pickPt(1)), "0.0000") & "," & Format(str(pickPt(2)), "0.0000") & vbCrLf & _
        "各户基点位置坐标："
        
        '开始绘图
        insertionPt(0) = pickPt(0) + output(5) / 2: insertionPt(2) = 0
        For n = 0 To (CInt(output(1)) - 1)
            insertionPt(1) = pickPt(1) + output(6) / 2
            For i = 0 To (CInt(output(3)) - 1)
                For j = 0 To (subnum - 1)
                    Set objBRef = ThisDrawing.ModelSpace.InsertBlock(insertionPt, strname, 1, 1, 1, 0)
                    objNew = objBRef.Explode
                    objBRef.Erase
                    insertionPt(1) = insertionPt(1) + y1
                    Form3.DebugText.Text = Form3.DebugText.Text + vbCrLf + str(insertionPt(0)) + "," + str(insertionPt(1)) + "," + str(insertionPt(2))
                Next j
                insertionPt(1) = insertionPt(1) + disty
                Form3.DebugText.Text = Form3.DebugText.Text + vbCrLf + str(insertionPt(0)) + "," + str(insertionPt(1)) + "," + str(insertionPt(2))
            Next i
            
            For i = 0 To (CInt(output(4)) - 1)
                Set objBRef = ThisDrawing.ModelSpace.InsertBlock(insertionPt, strname, 1, 1, 1, 0)
                Set objNew = objBRef.Explode
                objBRef.Erase
                insertionPt(1) = insertionPt(1) + y1
                Form3.DebugText.Text = Form3.DebugText.Text + vbCrLf + str(insertionPt(0)) + "," + str(insertionPt(1)) + "," + str(insertionPt(2))
            Next i
            insertionPt(0) = insertionPt(0) + x1 + distx
            Form3.DebugText.Text = Form3.DebugText.Text + vbCrLf + str(insertionPt(0)) + "," + str(insertionPt(1)) + "," + str(insertionPt(2))
        Next n
        
        ThisDrawing.SelectionSets.Item("SSet").Delete
        
        '插入文字
        If Form3.CheckBoxPrint.Value = True Then
        
            Dim mtextObj As AcadMText
            Dim mtextWidth As Double
            Dim mtextString As String
            Dim mtextPt(0 To 2) As Double
            
            mtextWidth = x0
            mtextString = _
            "地块尺寸：" & str(x0 / 1000) & "*" & str(y0 / 1000) & vbCrLf & _
            "基底面积：" & str(bsArea / 1000000) & vbCrLf & _
            "总户数：" & str(output(0) * sf) & vbCrLf & _
            "容积率：" & Format(str(output(7) * sf), "0.000") & vbCrLf & _
            "覆盖率：" & Format(str(output(8) * sf), "0.00%")
            mtextPt(0) = pickPt(0) + 1.5 * x0: mtextPt(1) = pickPt(0) + 0.5 * y0: mtextPt(2) = 0
            Set mtextObj = ThisDrawing.ModelSpace.AddMText(insertionPt, mtextWidth, mtextString)
            
        End If

        GoTo BACK


    


'Quit
ESC01:
    If MsgBox("输入数值不正确！按确认键重新输入", vbOKCancel) = vbOK Then
        GoTo BACK
    Else
        End
    End If
    GoTo BACK
ESC02:
    If MsgBox("错误！", vbOKCancel) = vbOK Then
        GoTo BACK
    Else
        End
    End If
    GoTo BACK
BACK:
    Form3.show
End Sub

Attribute VB_Name = "Form4"
Attribute VB_Base = "0{990B5E55-0966-4D90-9C7A-D7A9229239A3}{83344E06-7C30-4FF6-821B-D5CD6CCBC0B0}"
Attribute VB_GlobalNameSpace = False
Attribute VB_Creatable = False
Attribute VB_PredeclaredId = True
Attribute VB_Exposed = False
Attribute VB_TemplateDerived = False
Attribute VB_Customizable = False
Dim PolyInfo As QpBlockPointMat

Private Sub CmdBack_Click()
Form4.hide
Form2.show
End Sub

Private Sub CmdFindBlk_Click()
    Form4.hide
    'define variables
    Dim strname As String
    Dim objSS As AcadSelectionSet
    Dim objBlock As AcadBlock
    Dim objBRef As AcadBlockReference
    Dim objSourceEnts() As Object
    Dim varDestEnts As Variant
    Dim intI As Integer
    Dim dblOrigin(2) As Double
    Dim insertionPt(2) As Double
    Dim bsPt(2) As Double
    Dim pickPt As Variant
    Dim objNew As Object
    Dim currentTime As Date
    
    'initialize
    'ThisDrawing.PurgeAll
    
    'set the user input variable and origin
    currentTime = Now()
    strname = "QP_" & Format(currentTime, "MMDD_HHmmSS")

    
    'Selection set
    On Error Resume Next
        Set objSS = ThisDrawing.SelectionSets.Item("SSet")
    Set objSS = ThisDrawing.SelectionSets.Add("SSet")
    objSS.SelectOnScreen
    
    If objSS.Count = 0 Then GoTo BACK
    
    'Insertion point
    dblOrigin(0) = 0: dblOrigin(1) = 0: dblOrigin(2) = 0
    pickPt = ThisDrawing.Utility.GetPoint(dblOrigin, "Pick base point:")
    
    'put selected entities into an array for CopyObjects
    ReDim objSourceEnts(objSS.Count - 1)
    For intI = 0 To objSS.Count - 1
        Set objSourceEnts(intI) = objSS(intI)
    Next
    Form4.Label17.Caption = "选定图元数：" & str(objSS.Count)
    Form4.Label18.Caption = strname
    
    'create the 'empty' block using the given block name
    Set objBlock = ThisDrawing.Blocks.Add(pickPt, strname)

    'copy selected entities into the block
    varDestEnts = ThisDrawing.CopyObjects(objSourceEnts, objBlock)

    'clear
    objSS.Erase
    ThisDrawing.SelectionSets("SSet").Delete
    
    'show block reference
    Set objBRef = ThisDrawing.ModelSpace.InsertBlock(pickPt, strname, 1, 1, 1, 0)
    objNew = objBRef.Explode
    objBRef.Delete
    
BACK:
    Form4.show
End Sub

'地块多边形输入
Private Sub CmdFindPoly_Click()
    Dim polyBoundBox As QpShortCoordinateMat
    Form4.hide
    
    '获取多段线坐标
    PolyInfo = PolyCoord()
    If PolyInfo.err = True Then
        Form4.TextBox1.Text = "错误：未选择多段线!"
    Else
        Form4.TextBox1.Text = PolyInfo.AttributeString & vbCrLf & "顶点坐标："
        For i = 1 To PolyInfo.numPt
            Form4.TextBox1.Text = Form4.TextBox1.Text & vbCrLf & Format(PolyInfo.x(i), "0.0") & ", " & Format(PolyInfo.y(i), "0.0")
        Next i
    End If
    
    '计算包围盒
    polyBoundBox = Q_BoundBox(PolyInfo)
    Form4.show
End Sub

Private Sub CmdQuit_Click()
End
End Sub


'清空输入的数据
Private Sub CmdClear_Click()
    Form4.bSize1.Text = ""
    Form4.bSize2.Text = ""
    Form4.sSize1.Text = ""
    Form4.sSize2.Text = ""
    Form4.Area.Text = ""
    Form4.bsArea.Text = ""
    Form4.sdArea.Text = ""
    Form4.Dist1.Text = ""
    Form4.Dist2.Text = ""
    Form4.subnum.Text = ""
    Form4.dirAngle.Text = ""
    Form4.initialBack.Text = ""
End Sub


Private Sub CmdStart_Click()

    Dim dblOrigin(2) As Double
    Dim pickPt(2) As Double
    Dim sf As Double
    Dim gTol As Double   'global tolerance
    Dim inp As InputInfoMat
    Dim output As OutputCalcs
    Dim intialBackset As Double   '初始退距
    
    Form4.hide
    
    '选择插入点
    dblOrigin(0) = 0: dblOrigin(1) = 0: dblOrigin(2) = 0
    'pickPt = ThisDrawing.Utility.GetPoint(dblOrigin, "选取生成总图的基点(左下角):")
    pickPt(0) = dblOrigin(0): pickPt(1) = dblOrigin(1): pickPt(2) = dblOrigin(2)
    Set objBlock = ThisDrawing.Blocks.Item(strname)

    '从Form4读取数据
    If PolyInfo.numPt = 0 Then
        Form4.Results.Text = "未指定多边形"
        Form4.show
    Else
        If Form4.OptM.Value = True Then
            sf = 1#
        ElseIf Form4.OptMM.Value = True Then
            sf = 1000#
        End If
        inp.x1 = Val(Form4.sSize1.Text) * sf
        inp.y1 = Val(Form4.sSize2.Text) * sf
        inp.Area = Val(Form4.Area.Text) * sf * sf
        inp.sdArea = Val(Form4.sdArea.Text) * sf * sf
        inp.bsArea = Val(Form4.bsArea.Text) * sf * sf
        inp.distx = Val(Form4.Dist1.Text) * sf
        inp.disty = Val(Form4.Dist2.Text) * sf
        inp.subnum = Int(Val(Form4.subnum.Text))
        inp.strname = Form4.Label18.Caption
        inp.dirAngle = Val(Form4.dirAngle.Text)
        inp.radAngle = Val(Form4.dirAngle.Text) * 3.141593 / 180
        initialBackset = Val(Form4.initialBack.Text)
        gTol = Val(Form4.gTol.Text)
        output = main3plot(inp, PolyInfo, initialBackset)
        Form4.Results.Text = output.outputMsg & vbCrLf & "多边形地块内强排计算结果：" & vbCrLf & _
        "总户数：" & Format(output.sum, "0") & vbCrLf & _
        "容积率：" & Format(output.far, "0.000") & vbCrLf & _
        "实得容积率：" & Format(output.sdfar, "0.000") & vbCrLf & _
        "覆盖率：" & Format(output.cr, "0.00%")
        Form4.show
    End If
    

End Sub

Private Sub CommandButtonOK_Click()
    Dim dblOrigin(2) As Double
    Dim pickPt(2) As Double
    Dim sf As Double
    Dim gTol As Double   'global tolerance
    Dim inp As InputInfoMat
    Dim output As OutputCalcs
    Dim intialBackset As Double   '初始退距
    
    Form4.hide
    
    '选择插入点
    dblOrigin(0) = 0: dblOrigin(1) = 0: dblOrigin(2) = 0
    'pickPt = ThisDrawing.Utility.GetPoint(dblOrigin, "选取生成总图的基点(左下角):")
    pickPt(0) = dblOrigin(0): pickPt(1) = dblOrigin(1): pickPt(2) = dblOrigin(2)
    Set objBlock = ThisDrawing.Blocks.Item(strname)

    '从Form4读取数据
    If PolyInfo.numPt = 0 Then
        Form4.Results.Text = "未指定多边形"
        Form4.show
    Else
        If Form4.OptM.Value = True Then
            sf = 1#
        ElseIf Form4.OptMM.Value = True Then
            sf = 1000#
        End If
        inp.x1 = Val(Form4.sSize1.Text) * sf
        inp.y1 = Val(Form4.sSize2.Text) * sf
        inp.Area = Val(Form4.Area.Text) * sf * sf
        inp.bsArea = Val(Form4.bsArea.Text) * sf * sf
        inp.sdArea = Val(Form4.sdArea.Text) * sf * sf
        inp.distx = Val(Form4.Dist1.Text) * sf
        inp.disty = Val(Form4.Dist2.Text) * sf
        inp.subnum = Int(Val(Form4.subnum.Text))
        inp.strname = Form4.Label18.Caption
        inp.dirAngle = Val(Form4.dirAngle.Text)
        inp.radAngle = Val(Form4.dirAngle.Text) * 3.141593 / 180
        initialBackset = Val(Form4.initialBack.Text)
        gTol = Val(Form4.gTol.Text)
        output = main3(inp, PolyInfo, initialBackset)
        Form4.Results.Text = output.outputMsg & vbCrLf & "多边形地块内强排计算结果：" & vbCrLf & _
        "总户数：" & Format(output.sum, "0") & vbCrLf & _
        "容积率：" & Format(output.far, "0.000") & vbCrLf & _
        "实得容积率：" & Format(output.sdfar, "0.000") & vbCrLf & _
        "覆盖率：" & Format(output.cr, "0.00%")
        Form4.show
    End If
    
End Sub

'默认数据
Private Sub CommandDefault_Click()
    Form4.sSize1.Text = 7
    Form4.sSize2.Text = 10
    Form4.Area.Text = 155
    Form4.bsArea.Text = 60
    Form4.sdArea.Text = 175
    Form4.Dist1.Text = 6
    Form4.Dist2.Text = 13
    Form4.subnum.Text = 5
    Form4.dirAngle.Text = 15
    Form4.initialBack.Text = 20
End Sub

Attribute VB_Name = "Form5"
Attribute VB_Base = "0{1AA40A8D-1033-4E51-B23B-0C9FB47EF8E1}{A59B285A-AA3F-4479-ADF7-4338D7D2D6B8}"
Attribute VB_GlobalNameSpace = False
Attribute VB_Creatable = False
Attribute VB_PredeclaredId = True
Attribute VB_Exposed = False
Attribute VB_TemplateDerived = False
Attribute VB_Customizable = False
Dim PolyInfo As QpBlockPointMat


Private Sub CmdBack_Click()
Form5.hide
Form2.show
End Sub

'检索图块
Private Sub CmdFindBlk_Click()
    Dim strname As String
    Dim objBlock As Object
    
    strname = Form5.blkName.Text
    On Error Resume Next
    Set objBlock = ThisDrawing.Blocks.Item(strname)
    If err Then
        Form5.Label18.Caption = "错误！未找到此图块"
    Else
        Form5.Label18.Caption = "找到图块:" & strname
    End If

End Sub

'地块多边形输入
Private Sub CmdFindPoly_Click()
    Dim polyBoundBox As QpShortCoordinateMat
    Form5.hide
    
    '获取多段线坐标
    PolyInfo = PolyCoord()
    If PolyInfo.err = True Then
        Form5.TextBox1.Text = "错误：未选择多段线!"
    Else
        Form5.TextBox1.Text = PolyInfo.AttributeString & vbCrLf & "顶点坐标："
        For i = 1 To PolyInfo.numPt
            Form5.TextBox1.Text = Form5.TextBox1.Text & vbCrLf & Format(PolyInfo.x(i), "0.0") & ", " & Format(PolyInfo.y(i), "0.0")
        Next i
    End If
    
    '计算包围盒
    polyBoundBox = Q_BoundBox(PolyInfo)
    Form5.show
End Sub

Private Sub CmdImport_Click()
    'On Error Resume Next
    Dim xl, xb As Object
    Dim ImportNum As Integer
    Set xl = CreateObject("Excel.Application")
    xl.Visible = False
    'On Error Resume Next
    Set xlbook = xl.Workbooks.Open(ThisDrawing.Path & "\" & Form5.PathFile.Text)
    Set xlsheet = xl.Worksheets.Item("强排程序输入")
    ImportNum = Int(Form5.ImportNum.Text) + 1
    Form5.projName.Text = xlsheet.Cells(ImportNum, 2).Value
    Form5.sSize1.Text = xlsheet.Cells(ImportNum, 3).Value
    Form5.sSize2.Text = xlsheet.Cells(ImportNum, 4).Value
    Form5.Area.Text = xlsheet.Cells(ImportNum, 5).Value
    Form5.sdArea.Text = xlsheet.Cells(ImportNum, 6).Value
    Form5.bsArea.Text = xlsheet.Cells(ImportNum, 10).Value
    Form5.Dist1.Text = xlsheet.Cells(ImportNum, 7).Value
    Form5.Dist2.Text = xlsheet.Cells(ImportNum, 8).Value
    Form5.projName.Text = projName
    xlbook.Close
    xl.Quit
    Set xlsheet = Nothing
    Set xlbook = Nothing
    Set xl = Nothing
End Sub

Private Sub CmdQuit_Click()
End
End Sub


'清空输入的数据
Private Sub CmdClear_Click()
    Form5.bSize1.Text = ""
    Form5.bSize2.Text = ""
    Form5.sSize1.Text = ""
    Form5.sSize2.Text = ""
    Form5.Area.Text = ""
    Form5.bsArea.Text = ""
    Form5.sdArea.Text = ""
    Form5.Dist1.Text = ""
    Form5.Dist2.Text = ""
    Form5.subnum.Text = ""
    Form5.dirAngle.Text = ""
    Form5.initialBack.Text = ""
End Sub


Private Sub CmdStart_Click()

    Dim dblOrigin(2) As Double
    Dim pickPt(2) As Double
    Dim sf As Double
    Dim gTol As Double   'global tolerance
    Dim inp As InputInfoMat
    Dim output As OutputCalcs
    Dim intialBackset As Double   '初始退距
    
    Form5.hide
    
    '选择插入点
    dblOrigin(0) = 0: dblOrigin(1) = 0: dblOrigin(2) = 0
    'pickPt = ThisDrawing.Utility.GetPoint(dblOrigin, "选取生成总图的基点(左下角):")
    pickPt(0) = dblOrigin(0): pickPt(1) = dblOrigin(1): pickPt(2) = dblOrigin(2)

    '从Form4读取数据
    If PolyInfo.numPt = 0 Then
        Form5.Results.Text = "未指定多边形"
        Form5.show
    Else
        If Form5.OptM.Value = True Then
            sf = 1#
        ElseIf Form5.OptMM.Value = True Then
            sf = 1000#
        End If
        inp.x1 = Val(Form5.sSize1.Text) * sf
        inp.y1 = Val(Form5.sSize2.Text) * sf
        inp.Area = Val(Form5.Area.Text) * sf * sf
        inp.sdArea = Val(Form5.sdArea.Text) * sf * sf
        inp.bsArea = Val(Form5.bsArea.Text) * sf * sf
        inp.distx = Val(Form5.Dist1.Text) * sf
        inp.disty = Val(Form5.Dist2.Text) * sf
        inp.subnum = Int(Val(Form5.subnum.Text))
        inp.strname = Form5.blkName.Text
        inp.dirAngle = Val(Form5.dirAngle.Text)
        inp.radAngle = Val(Form5.dirAngle.Text) * 3.141593 / 180
        initialBackset = Val(Form5.initialBack.Text) * sf
        gTol = Val(Form5.gTol.Text)
        output = main3plot(inp, PolyInfo, initialBackset)
        Form5.Results.Text = output.outputMsg & vbCrLf & "多边形地块内强排计算结果：" & vbCrLf & _
        "总户数：" & Format(output.sum, "0") & vbCrLf & _
        "容积率：" & Format(output.far, "0.000") & vbCrLf & _
        "实得容积率：" & Format(output.sdfar, "0.000") & vbCrLf & _
        "覆盖率：" & Format(output.cr, "0.00%")
        Form5.show
    End If
    

End Sub

Private Sub CommandButtonOK_Click()
    Dim dblOrigin(2) As Double
    Dim pickPt(2) As Double
    Dim sf As Double
    Dim gTol As Double   'global tolerance
    Dim inp As InputInfoMat
    Dim output As OutputCalcs
    Dim intialBackset As Double   '初始退距
    Dim blkName As String   '户型图块名称
    
    Form5.hide
    
    '选择插入点
    dblOrigin(0) = 0: dblOrigin(1) = 0: dblOrigin(2) = 0
    'pickPt = ThisDrawing.Utility.GetPoint(dblOrigin, "选取生成总图的基点(左下角):")
    pickPt(0) = dblOrigin(0): pickPt(1) = dblOrigin(1): pickPt(2) = dblOrigin(2)
    Set objBlock = ThisDrawing.Blocks.Item(strname)

    '从Form5读取数据
    If PolyInfo.numPt = 0 Then
        Form5.Results.Text = "未指定多边形"
        Form5.show
    Else
        If Form5.OptM.Value = True Then
            sf = 1#
        ElseIf Form5.OptMM.Value = True Then
            sf = 1000#
        End If
        inp.x1 = Val(Form5.sSize1.Text) * sf
        inp.y1 = Val(Form5.sSize2.Text) * sf
        inp.Area = Val(Form5.Area.Text) * sf * sf
        inp.bsArea = Val(Form5.bsArea.Text) * sf * sf
        inp.sdArea = Val(Form5.sdArea.Text) * sf * sf
        inp.distx = Val(Form5.Dist1.Text) * sf
        inp.disty = Val(Form5.Dist2.Text) * sf
        inp.subnum = Int(Val(Form5.subnum.Text))
        inp.strname = Form5.Label18.Caption
        inp.dirAngle = Val(Form5.dirAngle.Text)
        inp.radAngle = Val(Form5.dirAngle.Text) * 3.141593 / 180
        initialBackset = Val(Form5.initialBack.Text) * sf
        gTol = Val(Form5.gTol.Text)
        output = main3(inp, PolyInfo, initialBackset)
        Form5.Results.Text = output.outputMsg & vbCrLf & "多边形地块内强排计算结果：" & vbCrLf & _
        "总户数：" & Format(output.sum, "0") & vbCrLf & _
        "容积率：" & Format(output.far, "0.000") & vbCrLf & _
        "实得容积率：" & Format(output.sdfar, "0.000") & vbCrLf & _
        "覆盖率：" & Format(output.cr, "0.00%")
        Form5.show
    End If
    
End Sub

'默认数据
Private Sub CommandDefault_Click()
    Form5.sSize1.Text = 7
    Form5.sSize2.Text = 10
    Form5.Area.Text = 155
    Form5.bsArea.Text = 60
    Form5.sdArea.Text = 175
    Form5.Dist1.Text = 6
    Form5.Dist2.Text = 13
    Form5.subnum.Text = 5
    Form5.dirAngle.Text = 15
    Form5.initialBack.Text = 20
End Sub

Attribute VB_Name = "FormOutput"
Attribute VB_Base = "0{FDCD3690-1CAD-4205-9F6E-A86CC775D2F6}{AC9A8619-AD4D-40F1-B2AC-3BE23205C6A2}"
Attribute VB_GlobalNameSpace = False
Attribute VB_Creatable = False
Attribute VB_PredeclaredId = True
Attribute VB_Exposed = False
Attribute VB_TemplateDerived = False
Attribute VB_Customizable = False
Private Sub CommandButton1_Click()

FormOutput.hide
Form1.show

End Sub

Attribute VB_Name = "Module1"
'Type 定义
Public Type QpShortCoordinateMat
    x(20) As Double
    y(20) As Double
    z(20) As Double
    num As Integer
    outputStr As String
End Type

Public Type QpLongCoordinateMat
    x(100) As Double
    y(100) As Double
    z(100) As Double
    num As Integer
    outputStr As String
End Type

Public Type QpPoint
    x As Double
    y As Double
    z As Double
    err As Boolean
End Type

Public Type Qp2dPoint
    x As Double
    y As Double
    err As Boolean
End Type

Public Type QpBlockPointMat '多边形地块信息存储
    x(50) As Double
    y(50) As Double
    z(50) As Double
    Area As Double
    numPt As Integer
    AttributeString As String
    err As Boolean
End Type


Public Type QpVector '向量
    x(100) As Double
    num As Integer
    outputStr As String
    err As Boolean
End Type


'主程序
Sub QPSTART()
    Form2.show
End Sub



'*********************将三个变量转换成一个点坐标变量*********
Public Function Point3D(ByVal x As Double, ByVal y As Double, Optional z As Double = 0) As Variant
    Dim retVal(0 To 2) As Double
    retVal(0) = x: retVal(1) = y: retVal(2) = z
    Point3D = retVal
End Function
'***************************************************************

'*********************通过两个对角点绘制矩形********************
Public Function Rectangle(Point1, Point2) As AcadLWPolyline

    Dim vertices(0 To 7) As Double, PL As AcadLWPolyline
    
    vertices(0) = CDbl(Point1(0)): vertices(1) = CDbl(Point1(1))
    vertices(2) = CDbl(Point2(0)): vertices(3) = CDbl(Point1(1))
    vertices(4) = CDbl(Point2(0)): vertices(5) = CDbl(Point2(1))
    vertices(6) = CDbl(Point1(0)): vertices(7) = CDbl(Point2(1))

    Set PL = ThisDrawing.ModelSpace.AddLightWeightPolyline(vertices)
    PL.Closed = True
    
    Set Rectangle = PL
End Function
'***************************************************************


'*********************读取2D多段线坐标********************
Public Function PolyCoord() As QpBlockPointMat
    Dim SSet As AcadSelectionSet
    Dim ent As AcadLWPolyline
    Dim fType() As Integer, fData() As Variant
    Dim i As Long, j As Long        '多边形各点坐标（注意！最后一个点坐标是起点坐标，围合成多边形）
    Dim dbCor As Variant
    Dim numPt As Integer  '多边形顶点数量
    Dim ytemp As Double
    
    On Error Resume Next
        Set SSet = ThisDrawing.SelectionSets.Item("sPoly")
    Set SSet = ThisDrawing.SelectionSets.Add("sPoly")
    
    '屏幕选取多段线+过滤器
    ReDim fType(0), fData(0)
    fType(0) = 0: fData(0) = "LWPOLYLINE" '这里表示2D多义线
    SSet.SelectOnScreen fType, fData

    '读取多段线顶点坐标
    For Each ent In SSet
        If ent.Closed = False Then
            PolyCoord.numPt = (UBound(ent.Coordinates) - 1) \ 2
            PolyCoord.Area = ent.Area
            If ent.Area = 0 Then
                PolyCoord.err = True
                GoTo ErrReturn
            Else
                PolyCoord.err = False
            End If
            PolyCoord.AttributeString = "顶点数：" & str(PolyCoord.numPt) & vbCrLf & "地块面积：" & Format(ent.Area, "0.0")
            'loop for all points
            For j = 0 To PolyCoord.numPt
                PolyCoord.x(j) = ent.Coordinates(j * 2)
                PolyCoord.y(j) = ent.Coordinates(j * 2 + 1)
                PolyCoord.z(j) = 0
            Next
            '补全最后一个点
            PolyCoord.x(j + 1) = ent.Coordinates(0)
            PolyCoord.y(j + 1) = ent.Coordinates(1)
            PolyCoord.z(j + 1) = 0
            'loop for all coordinates
            GoTo out
        Else
            PolyCoord.numPt = (UBound(ent.Coordinates) - 1) \ 2 + 1
            PolyCoord.Area = ent.Area
            If ent.Area = 0 Then
                PolyCoord.err = True
                GoTo ErrReturn
            Else
                PolyCoord.err = False
            End If
            PolyCoord.AttributeString = "顶点数：" & str(PolyCoord.numPt) & vbCrLf & "地块面积：" & Format(ent.Area, "0.0")
            'loop for all points
            PolyCoord.x(0) = ent.Coordinate(0)
            PolyCoord.y(0) = ent.Coordinate(1)
            PolyCoord.z(0) = 0
            For j = 1 To PolyCoord.numPt
                PolyCoord.x(j) = ent.Coordinates(j * 2)
                PolyCoord.y(j) = ent.Coordinates(j * 2 + 1)
                PolyCoord.z(j) = 0
            Next
            '补全最后一个点
            PolyCoord.x(j + 1) = ent.Coordinates(0)
            PolyCoord.y(j + 1) = ent.Coordinates(1)
            PolyCoord.z(j + 1) = 0
            'loop for all coordinates
            GoTo out
        End If
    Next

ErrReturn:
    SSet.Clear
    SSet.Delete
    PolyCoord.err = True
    Call MsgBox("未选定多段线，请重新选择！", vbOKOnly)
    GoTo endfunc

out:
    SSet.Clear
    SSet.Delete
    
endfunc:
End Function
'***************************************************************





'*************************QpPoint 转换为 CAD点坐标***********************
Public Function Q_qp2cad(InputPt As QpPoint) As Double()
    Q_qp2cad(0) = InputPt.x
    Q_qp2cad(1) = InputPt.y
    Q_qp2cad(2) = InputPt.z
        If InputPt.z = "" Then Q_qp2cad(2) = 0
End Function
'************************************************************************


'*************************跨立试验***********************
Public Function isLineSegmentCross(p1 As QpPoint, p2 As QpPoint, q1 As QpPoint, q2 As QpPoint) As Boolean


    If ((q1.x - p1.x) * (q1.y - q2.y) - (q1.y - p1.y) * (q1.x - q2.x)) * ((q1.x - p2.x) * (q1.y - q2.y) - (q1.y - p2.y) * (q1.x - q2.x)) < 0 Or _
        ((p1.x - q1.x) * (p1.y - p2.y) - (p1.y - q1.y) * (p1.x - p2.x)) * ((p1.x - q2.x) * (p1.y - p2.y) - (p1.y - q2.y) * (p1.x - p2.x)) < 0 Then
        isLineSegmentCross = True
    Else
        isLineSegmentCross = False
    End If
    
End Function
'************************************************************************


'************************冒泡排序***********************
Public Function sort(a() As Double, n As Integer)
    Dim i As Integer, j As Integer, temp As Double, k As Integer
    For i = 0 To n - 1
        k = i
            For j = i + 1 To n
                If a(j) < a(k) Then k = j
            Next j
        temp = a(k): a(k) = a(i): a(i) = temp
    Next i
End Function
'************************************************************************





'矩形盲排计算
Public Function Q_RecArrS(x0 As Double, y0 As Double, x1 As Double, y1 As Double, Area As Double, bsArea As Double, distx As Double, disty As Double, subnum As Integer, arrDir As Integer) As Double()
    Dim numxs As Integer   'number of standard sub-blocks
    Dim numxp As Integer  'number of non-standard sub-blocks
    Dim subsize As Double   'size of standard sub-blocks
    Dim numys As Integer    'number of standard sub-blocks
    Dim numyp As Integer  'number of non-standard sub-blocks
    Dim totalNum As Integer
    Dim rx As Double  'residue x
    Dim ry As Double  'residue y
    Dim output(0 To 10) As Double
    
    '纵向联排
    If arrDir = 1 Then

        
        ' y direction: number of standard sub-block
        subsize = subnum * y1 + disty
        numys = Int(y0 / subsize)
        ry = (y0 - numys * subsize + disty)
        
        ' y direction: number of non-standard sub-block
        If ry >= (disty + y1) Then
            numyp = Int((ry - disty) / y1)
            ry = y0 - numys * subsize - numyp * y1
        Else
            numyp = 0
        End If
            
        ' x direction: number of standard sub-block
        subsize = x1 + distx
        numxs = Int(x0 / subsize)
        rx = x0 - numxs * subsize + distx
        numxp = 0
        
        ' calculations
        output(0) = (numxs + numxp) * (numys * subnum + numyp)
        output(1) = CDbl(numxs)
        output(2) = CDbl(numxp)
        output(3) = CDbl(numys)
        output(4) = CDbl(numyp)
        output(5) = rx
        output(6) = ry
        output(7) = Area * output(0) / (x0 * y0)
        output(8) = bsArea * output(0) / (x0 * y0)
        
    End If
    Q_RecArrS = output

End Function


'矩形盲排绘图坐标计算
Public Function Q_RecCoorS(pickPt() As Double, x0 As Double, y0 As Double, x1 As Double, y1 As Double, Area As Double, bsArea As Double, distx As Double, disty As Double, subnum As Integer, arrDir As Integer) As QpLongCoordinateMat
  
    '纵向联排
    If arrDir = 1 Then
        Dim output As Double
        Dim ii As Integer, i As Integer, j As Integer, n As Integer
        output = Q_RecArrS(x0, y0, x1, y1, Area, bsArea, distx, disty, subnum, arrDir)
        '插入点
        ii = 0
        Q_RecCoorS.x(0) = pickPt(0) + output(5) / 2: Q_RecCoorS.y(0) = 0
        For n = 1 To (CInt(output(1)) - 1)
            Q_RecCoorS.y(ii) = pickPt(1) + output(6) / 2
            For i = 0 To (CInt(output(3)) - 1)
                For j = 0 To (subnum - 1)
                    ii = ii + 1
                    Q_RecCoorS.y(ii) = Q_RecCoorS.y(ii - 1) + y1
                    Form1.DebugText.Text = Form1.DebugText.Text + vbCrLf + str(insertionPt(0)) + "," + str(insertionPt(1)) + "," + str(insertionPt(2))
                Next j
                Q_RecCoorS.y(ii + 1) = Q_RecCoorS.y(ii) + disty
                Form1.DebugText.Text = Form1.DebugText.Text + vbCrLf + str(insertionPt(0)) + "," + str(insertionPt(1)) + "," + str(insertionPt(2))
            Next i
            
            For i = 0 To (CInt(output(4)) - 1)
                ii = ii + 1
                Q_RecCoorS.y(ii) = Q_RecCoorS.y(ii - 1) + y1
                Form1.DebugText.Text = Form1.DebugText.Text + vbCrLf + str(insertionPt(0)) + "," + str(insertionPt(1)) + "," + str(insertionPt(2))
            Next i
            insertionPt(0) = insertionPt(0) + x1 + distx
            Form1.DebugText.Text = Form1.DebugText.Text + vbCrLf + str(insertionPt(0)) + "," + str(insertionPt(1)) + "," + str(insertionPt(2))
        Next n
        
    End If
    

End Function

Attribute VB_Name = "Module2"
Public Function Q_Intersecx(inputpoly As QpBlockPointMat, ByVal yi As Double, ByVal GridTolerance As Double) As QpShortCoordinateMat
    Dim i As Integer, j As Integer
    Dim ymin As Double
    Dim boundBox As QpShortCoordinateMat
    Dim tolx As Double, toly As Double
    
    '容许误差：GridTolerance为计算总体相对误差
    tolx = GridTolerance * (boundBox.x(1) - boundBox.x(0)) 'x边误差值
    toly = GridTolerance * (boundBox.y(1) - boundBox.y(0)) 'y边误差值
    
    boundBox = Q_BoundBox(inputpoly)
    If (yi > boundBox.x(0) And yi < boundBox.x(1)) Then
        j = 0
        For i = 1 To (inputpoly.numPt + 1) '遍历多边形每条边
            If yi > (inputpoly.y(i - 1) - toly) And yi < (inputpoly.y(i - 1) + toly) Then   '特殊情况：奇数个交点
                If yi > (inputpoly.y(i) - toly) And yi < (inputpoly.y(i) + toly) Then   '边与直线重合
                    Q_Intersecx.x(j) = inputpoly.x(i - 1)
                    Q_Intersecx.x(j + 1) = inputpoly.x(i)
                    Q_Intersecx.y(j) = yi
                    Q_Intersecx.y(j + 1) = yi
                    j = j + 2

            Else  '普通情况：偶数个交点
                
                If (inputpoly.y(i - 1) > (yi + toly) And inputpoly.y(i) < (yi - toly)) Then     '扫描线穿过边
                    ymin = inputpoly.y(i)
                    Q_Intersecx.x(j) = (yi - ymin) * (inputpoly.x(i) - inputpoly.x(i - 1)) / (inputpoly.y(i) - inputpoly.y(i - 1))
                    Q_Intersecx.y(j) = yi
                    j = j + 1
                ElseIf (inputpoly.y(i - 1) < yi And inputpoly.y(i) > yi) Then    '扫描线穿过边
                    ymin = inputpoly.y(i - 1)
                    Q_Intersecx.x(j) = (yi - ymin) * (inputpoly.x(i) - inputpoly.x(i - 1)) / (inputpoly.y(i) - inputpoly.y(i - 1))
                    Q_Intersecx.y(j) = yi
                    j = j + 1
                End If
                
            End If
            
        Next i
    Else
        Q_Intersecx.x(0) = 0
    End If
    Call sort(Q_Intersecx.x, inputpoly.numPt)
    Q_Intersecx.num = j
End Function


Public Function Q_IntersecDist(inputpoly As QpBlockPointMat, ByVal yi As Double, ByVal GridTolerance As Double) As QpVector
    Dim i As Integer
    Dim InputIntersec As QpShortCoordinateMat
    InputIntersec = Q_Intersecx(inputpoly, yi, GridTolerance)
    For i = 0 To (InputIntersec.num - 1) \ 2
        Q_IntersecDist(i) = InputIntersec.x(2 * i) - InputIntersec.x(2 * i + 2)
    Next i
End Function

Attribute VB_Name = "Module3"
Public Type InputInfoMat
    x0 As Double
    y0 As Double
    x1 As Double
    y1 As Double
    Area As Double
    sdArea As Double
    bsArea As Double
    distx As Double
    disty As Double
    subnum As Integer
    arrDir As Integer
    strname As String
    dirAngle As Double
    radAngle As Double
End Type

Public Type OutputCalcs
    sum As Integer
    far As Double
    sdfar As Double
    cr As Double
    outputMsg As String
    numxs(51, 3) As Integer
    numxp(51, 3) As Integer
    rx(51, 3) As Double
End Type

Private Type pt
    x As Double
    y As Double
    err As Boolean
End Type

Private Type QpIntersec
    ptIntersec0(11) As pt
    ptIntersec1(11) As pt
    sec(21) As Double
    num As Integer
    err As Boolean
End Type

Private Type QpLine
    a As pt
    b As pt
End Type


Public Const eps = 0.0001
Public inum(201, 4) As Integer
Dim Backset(201) As Double    '迭代退距


Private Function cmp(a As pt, b As pt) As Boolean
    If Abs(a.x - b.x) < eps Then
        cmp = True
    Else
        cmp = False
    End If
End Function

' 最值
Private Function max(ByVal a As Double, ByVal b As Double) As Double
    If a > b Then
        max = a
    Else
        max = b
    End If
End Function

Private Function min(ByVal a As Double, ByVal b As Double) As Double
    If a > b Then
        min = b
    Else
        min = a
    End If
End Function


' 求距离
Private Function dist(a As pt, b As pt)
    dist = Sqr((a.x - b.x) * (a.x - b.x) + (a.y - b.y) * (a.y - b.y))
End Function


' 求方向
Private Function direction(pi As pt, pj As pt, pk As pt)
    direction = (pk.x - pi.x) * (pj.y - pi.y) - (pj.x - pi.x) * (pk.y - pi.y)
End Function


' 判断点在线段上
Private Function on_segment(pi As pt, pj As pt, pk As pt)
    If direction(pi, pj, pk) = 0 Then
        If pk.x >= min(pi.x, pj.x) And pk.x <= max(pi.x, pj.x) And pk.y >= min(pi.y, pj.y) And pk.y <= max(pi.y, pj.y) _
        Then on_segment = True
    Else
    on_segment = False
    End If
End Function


' 判断线段相交
Private Function segments_intersect(p1 As pt, p2 As pt, p3 As pt, p4 As pt) As Boolean
    Dim d1 As Double, d2 As Double, d3 As Double, d4 As Double
    d1 = direction(p3, p4, p1)
    d2 = direction(p3, p4, p2)
    d3 = direction(p1, p2, p3)
    d4 = direction(p1, p2, p4)
    If d1 * d2 < 0 And d3 * d4 < 0 Then
        segments_intersect = True
    ElseIf d1 = 0 And on_segment(p3, p4, p1) Then
        segments_intersect = True
    ElseIf d2 = 0 And on_segment(p3, p4, p2) Then
        segments_intersect = True
    ElseIf d3 = 0 And on_segment(p1, p2, p3) Then
        segments_intersect = True
    ElseIf d4 = 0 And on_segment(p1, p2, p4) Then
        segments_intersect = True
    Else
        segments_intersect = False
    End If
End Function


' 计算交点坐标
Private Function intersection(a1 As pt, a2 As pt, b1 As pt, b2 As pt) As pt
    Dim ret As pt
    Dim t As Double
    ret = a1
    t = ((a1.x - b1.x) * (b1.y - b2.y) - (a1.y - b1.y) * (b1.x - b2.x)) / ((a1.x - a2.x) * (b1.y - b2.y) - (a1.y - a2.y) * (b1.x - b2.x))
    ret.x = ret.x + (a2.x - a1.x) * t
    ret.y = ret.y + (a2.y - a1.y) * t
    intersection = ret
End Function


'*************************输出包围盒角点坐标***********************
Public Function Q_BoundBox(inputpoly As QpBlockPointMat) As QpShortCoordinateMat
    Dim j As Integer
    Q_BoundBox.x(0) = inputpoly.x(0)
    Q_BoundBox.y(0) = inputpoly.y(0)
    Q_BoundBox.x(1) = inputpoly.x(0)
    Q_BoundBox.y(1) = inputpoly.y(0)
    For j = 0 To inputpoly.numPt
        If inputpoly.x(j) < Q_BoundBox.x(0) Then Q_BoundBox.x(0) = inputpoly.x(j)
        If inputpoly.y(j) < Q_BoundBox.y(0) Then Q_BoundBox.y(0) = inputpoly.y(j)
        If inputpoly.x(j) > Q_BoundBox.x(1) Then Q_BoundBox.x(1) = inputpoly.x(j)
        If inputpoly.y(j) > Q_BoundBox.y(1) Then Q_BoundBox.y(1) = inputpoly.y(j)
    Next j
    Q_BoundBox.num = 1
End Function
'***************************************************************


' 判断点是否在多边形内, n - 多边形边数
Private Function InPolygon(a As pt, ByVal n As Integer, inputpoly As QpBlockPointMat) As Boolean
    Dim i As Integer
    Dim b As pt, c As pt, d As pt
    Dim flag As Integer, cound As Integer
    Dim bool As Integer
    flag = 0: Count = 0
    
    b.y = a.y
    b.x = 100000000    '射线
    
    For i = 0 To n - 1
        c.x = inputpoly.x(i)
        c.y = inputpoly.y(i)
        d.x = inputpoly.x(i + 1)
        d.y = inputpoly.y(i + 1)
        If on_segment(c, d, a) = True Then InPolygon = 1   '点在多边形一条边上
        If Abs(c.y - d.y) < eps Then GoTo CONTINUE
        If on_segment(a, b, c) = True Then  '和顶点相交
            If c.y > d.y Then Count = Count + 1
        ElseIf on_segment(a, b, d) = True Then   '和顶点相交
            If d.y > c.y Then Count = Count + 1
        ElseIf segments_intersect(a, b, c, d) = True Then  '和边相交
            Count = Count + 1
        End If
CONTINUE:
    Next i
    '判断奇偶数
    bool = Count Mod 2
    If bool = 1 Then    '奇数：点在多边形内
        InPolygon = True
    Else
        InPolygon = False
    End If
End Function

'判断是否相交
Private Function isIntersec(s As pt, e As pt, a As pt, b As pt) As Boolean

    If direction(e, a, s) * direction(e, b, s) <= 0 Then
        isIntersec = True
    Else
        isIntersec = False
    End If

End Function


'************************点集冒泡排序2***********************
Public Function sort2(a() As pt, n As Integer)
    Dim i As Integer, j As Integer, temp As Double, k As Integer
    i = 0: j = 0: k = 0
    For i = 0 To n - 1
        k = i
            For j = i + 1 To n
                If a(j).x < a(k).x Then k = j
            Next j
        temp = a(k).x: a(k).x = a(i).x: a(i).x = temp
        temp = a(k).y: a(k).y = a(i).y: a(i).y = temp
    Next i
End Function
'************************************************************************


' 计算交点 ( n - 多边形边数 )
Private Function findIntersec(s As pt, e As pt, inputpoly As QpBlockPointMat) As QpIntersec
    Dim i As Integer, j As Integer, k As Integer
    Dim n As Integer
    Dim a As pt, b As pt, temp As pt
    i = 0: j = 0: k = 0
    
    n = inputpoly.numPt
    ReDim gtemp(n) As pt
    'ReDim gtemp(n)
    For i = 0 To n      '多边形点向量最后一点必须为起点！
        a.x = inputpoly.x(i)
        a.y = inputpoly.y(i)
        b.x = inputpoly.x(i + 1)
        b.y = inputpoly.y(i + 1)
        If Abs(direction(e, a, s)) < eps And Abs(direction(e, b, s)) < eps Then
            gtemp(k) = a
            k = k + 1
            gtemp(k) = b
            k = k + 1
        ElseIf isIntersec(s, e, a, b) = True Then '两直线相交
            gtemp(k) = intersection(s, e, a, b)   '两直线交点
            k = k + 1
        End If
    Next i
    
    If k = 0 Then
        err = True
        findIntersec.num = 0
        GoTo ENDFUNCIntersec
    End If
    
    Call sort2(gtemp, k)     '排序点集
    
    j = 0
    For i = 1 To k - 1
        a = gtemp(i)
        b = gtemp(i + 1)
        temp.x = (a.x + b.x) / 2
        temp.y = (a.y + b.y) / 2
        If InPolygon(temp, n, inputpoly) = True Then
            findIntersec.sec(j) = dist(a, b)    '割线长度
            If a.x < b.x Then
                findIntersec.ptIntersec0(j) = a: findIntersec.ptIntersec1(j) = b  '割线左顶点
            Else
                findIntersec.ptIntersec0(j) = b: findIntersec.ptIntersec1(j) = a '割线右顶点
            End If
            j = j + 1
        End If
    Next i
    findIntersec.num = j '割线数量
    err = False
ENDFUNCIntersec:
End Function


' 获取左下端点  lower left vertex
Private Function findVertexLL(inputpoly As QpBlockPointMat, boundBox As QpShortCoordinateMat, ByVal backDist As Double) As pt
    Dim n As Integer, i As Integer, j As Integer
    Dim p0() As pt, temp As pt
    
    n = inputpoly.numPt

    ReDim p0(n)
    p0(0).x = inputpoly.x(0)
    p0(0).y = inputpoly.y(0)
    
    '找y坐标在包围盒底部+-初始退距附近的点集
    j = 0
    For i = 0 To n
        If Abs(inputpoly.y(i) - boundBox.y(0)) < backDist Then
            p0(j).y = inputpoly.y(i): p0(j).x = inputpoly.x(i)
            j = j + 1
        End If
    Next i
    temp.x = p0(0).x: temp.y = p0(0).y
    '在点集中找横坐标最小的点
    For i = 0 To j - 1
        If p0(i).x < temp.x Then
            temp.x = p0(i).x
            temp.y = p0(i).y
        End If
    Next i
    findVertexLL = temp
End Function



' 获取右下顶点 lower right vertex
Private Function findVertexLR(inputpoly As QpBlockPointMat, boundBox As QpShortCoordinateMat, ByVal backDist As Double) As pt
    Dim n As Integer, i As Integer, j As Integer
    Dim p0() As pt, temp As pt
    
    n = inputpoly.numPt
    
    ReDim p0(n)
    p0(0).x = inputpoly.x(0)
    p0(0).y = inputpoly.y(0)
    
    '找y坐标在包围盒底部+初始退距附近的点集
    j = 0
    For i = 0 To n
        If Abs(inputpoly.y(i) - boundBox.y(0)) < backDist Then
            p0(j).y = inputpoly.y(i): p0(j).x = inputpoly.x(i)
            j = j + 1
        End If
    Next i
    temp.x = p0(0).x: temp.y = p0(0).y
    '在点集中找横坐标最大的点
    For i = 0 To j - 1
        If p0(i).x > temp.x Then
            temp.x = p0(i).x
            temp.y = p0(i).y
        End If
    Next i
    findVertexLR = temp
End Function


' 建立东西扫描线, radAngle为方向角弧度值(-90<dirAngle<90)，正东为0，逆时针为正
Private Function scanLineEW(cornerPt As pt, ByVal radAngle As Double, ByVal boundx1 As Double, ByVal boundx2 As Double) As QpLine
    Dim stan As Double
    Dim temp As pt
    stan = Tan(radAngle)
    scanLineEW.a.x = boundx1
    scanLineEW.b.x = boundx2
    scanLineEW.a.y = cornerPt.y - (cornerPt.x - boundx1) * stan
    scanLineEW.b.y = cornerPt.y + (boundx2 - cornerPt.x) * stan
End Function



'割线上排布户型单元
Private Function insertUnit(a As pt, ByVal rx As Double, ByVal numxs As Double, ByVal numxp As Double, inp As InputInfoMat) As Double
    Dim insertionPt(2) As Double
    Dim dx As Double, dy As Double
    Dim objBlock As AcadBlock
    Dim objBRef As AcadBlockReference
    Dim objNew As Object
    
    dx = Cos(inp.radAngle)
    dy = Sin(inp.radAngle)
    insertionPt(0) = a.x + rx * dx
    insertionPt(1) = a.y + rx * dy
    insertionPt(2) = 0
    
    'Set objBlock = ThisDrawing.Blocks.Item(inp.strname)
    '标准
    For i = 0 To (numxs - 1)
        For j = 0 To (inp.subnum - 1)
            Set objBRef = ThisDrawing.ModelSpace.InsertBlock(insertionPt, inp.strname, 1, 1, 1, inp.radAngle)
            'objNew = objBRef.Explode
            'objBRef.Erase
            insertionPt(0) = insertionPt(0) + inp.x1 * dx
            insertionPt(1) = insertionPt(1) + inp.x1 * dy
        Next j
        insertionPt(0) = insertionPt(0) + inp.distx * dx
        insertionPt(1) = insertionPt(1) + inp.distx * dy
    Next i
    '非标准
    For i = 0 To (numxp - 1)
        Set objBRef = ThisDrawing.ModelSpace.InsertBlock(insertionPt, inp.strname, 1, 1, 1, inp.radAngle)
        'Set objNew = objBRef.Explode
        'objBRef.Erase
        insertionPt(0) = insertionPt(0) + inp.x1 * dx
        insertionPt(1) = insertionPt(1) + inp.x1 * dy
    Next i
End Function


' module3主程序
Public Function main3(inp As InputInfoMat, inputpoly As QpBlockPointMat, ByVal initialBackset As Double) As OutputCalcs
    Dim boundBox As QpShortCoordinateMat
    Dim scanLine As QpLine
    Dim a As pt, b As pt, cornerPt As pt, c As pt, d As pt
    Dim dx As Double, dy As Double
    Dim tempbool As Boolean
    Dim radAngle As Double  '转轴角度
    
    Dim iDist As Double
    Dim secnum As Integer    '计算过程中的割线数存储
    Dim sum As Integer      '总户数
    
    Dim boundsizex As Double, boundsizey As Double, boundDist As Double   '包围盒大小
    Dim intersec1 As QpIntersec, intersec2 As QpIntersec, intersec3 As QpIntersec   '交点输出
    'Dim line1(2) As Double, line2(2) As Double  '测试用
    
    Dim i As Integer, k As Integer, j As Integer
    Dim dtan As Double, dsin As Double, dcos As Double
    Dim subsize As Double   'size of standard sub-blocks
    
    '初始化
    i = 0: j = 0: k = 0
    sum = 0
    tempbool = False
    dsin = Sin(inp.radAngle)
    dcos = Cos(inp.radAngle)
    dtan = dsin / dcos
    
    
    '获取多边形数据
    'InputPoly = PolyCoord()
    n = inputpoly.numPt

    '获取多边形包围盒
    boundBox = Q_BoundBox(inputpoly)
    boundsizex = boundBox.x(1) - boundBox.x(0)
    boundsizey = boundBox.y(1) - boundBox.y(0)
    boundDist = Sqr(boundsizex * boundsizex + boundsizey * boundsizey)
    
    '获取起算点
    If inp.dirAngle > 0 Then
        cornerPt = findVertexLR(inputpoly, boundBox, initialBackset)
    Else
        cornerPt = findVertexLL(inputpoly, boundBox, initialBackset)
    End If
    
    '起算线(东西方向)
    If inp.dirAngle < 90 And inp.dirAngle > -90 Then
        radAngle = inp.dirAngle * 3.14159265 / 180
        scanLine = scanLineEW(cornerPt, radAngle, boundBox.x(0), boundBox.x(1))
        dx = Sin(radAngle): dy = 1 / Cos(radAngle)
        a.x = boundBox.x(0): b.x = boundBox.x(1)
        
        '检查并计算第一条扫描线（初始扫描线）
        i = 0
        Backset(i) = initialBackset
        a.y = scanLine.a.y + Backset(i) * dy: b.y = scanLine.b.y + Backset(i) * dy
        intersec1 = findIntersec(a, b, inputpoly)         '由扫描线找交点，返回交点数据库
        If intersec1.num <= 0 Then
            'Call MsgBox("初始扫描线与地块无交点！", vbOKCancel)
            main3.outputMsg = main3.outputMsg + "初始扫描线：与地块无交点"
            GoTo ENDFUNCTEST
        Else
            For i = 0 To intersec1.num - 1
                If intersec1.sec(i) > inp.x1 Then tempbool = True
                Next i
        End If
        
        '从南向北扫描，横向联排
        sum = 0: i = 0: j = 0: k = 0
        If tempbool = True Then
            main3.outputMsg = main3.outputMsg + "检查初始扫描线：成功！"
            Do
                '扫描线1
                a.y = scanLine.a.y + Backset(k) * dy: b.y = scanLine.b.y + Backset(k) * dy
                intersec1 = findIntersec(a, b, inputpoly)         '由扫描线找交点，返回交点数据库
                k = k + 1

                '前进一个进深,扫描线2
                Backset(k) = Backset(k - 1) + inp.y1
                a.y = scanLine.a.y + Backset(k) * dy: b.y = scanLine.b.y + Backset(k) * dy
                intersec2 = findIntersec(a, b, inputpoly)         '由扫描线找交点，返回交点数据库
                
                If intersec2.num <= 0 Then
                    Exit Do
                Else
                    secnum = max(intersec1.num, intersec2.num)
                End If
                For j = 0 To secnum - 1
                    '绘制测试扫描线
                    'line1(0) = intersec1.ptIntersec0(j).x: line1(1) = intersec1.ptIntersec0(j).y: line1(2) = 0
                    'line2(0) = intersec1.ptIntersec1(j).x: line2(1) = intersec1.ptIntersec1(j).y: line2(2) = 0
                    'Call ThisDrawing.ModelSpace.AddLine(line1, line2)
                    'line1(0) = intersec2.ptIntersec0(j).x: line1(1) = intersec2.ptIntersec0(j).y: line1(2) = 0
                    'line2(0) = intersec2.ptIntersec1(j).x: line2(1) = intersec2.ptIntersec1(j).y: line2(2) = 0
                    'Call ThisDrawing.ModelSpace.AddLine(line1, line2)

                    '计算户数
                    '左侧起排点
                    If intersec2.ptIntersec0(j).x < (intersec1.ptIntersec0(j).x - inp.y1 * dsin) Then
                        c.x = intersec1.ptIntersec0(j).x
                        c.y = intersec1.ptIntersec0(j).y
                    Else
                        c.x = intersec2.ptIntersec0(j).x + inp.y1 * dtan * dcos
                        c.y = intersec1.ptIntersec0(j).y + (intersec2.ptIntersec0(j).x - intersec1.ptIntersec0(j).x) * dtan + inp.y1 * dtan * dsin
                    End If
                    
                    '右侧终排点
                    If intersec2.ptIntersec1(j).x > (intersec1.ptIntersec1(j).x - inp.y1 * dsin) Then
                        d.x = intersec1.ptIntersec1(j).x
                        d.y = intersec1.ptIntersec1(j).y
                    Else
                        d.x = intersec2.ptIntersec1(j).x + inp.y1 * dsin
                        d.y = intersec2.ptIntersec1(j).y - inp.y1 * dcos
                    End If
                    
                    '真割线长度
                    iDist = dist(c, d)
                    
                    '标准组团
                    subsize = inp.subnum * inp.x1 + inp.distx
                    main3.numxs(i, j) = Int(iDist / subsize)
                    main3.rx(i, j) = (iDist - main3.numxs(i, j) * subsize + inp.distx)
                    
                    '非标准组团
                    If main3.rx(i, j) >= (inp.distx + inp.x1) Then
                        main3.numxp(i, j) = Int((main3.rx(i, j) - inp.distx) / inp.x1)
                        main3.rx(i, j) = iDist - main3.numxs(i, j) * subsize - main3.numxp(i, j) * inp.x1
                    Else
                        main3.numxp(i, j) = 0
                    End If
                    inum(i, j) = main3.numxs(i, j) * inp.subnum + main3.numxp(i, j)
                    sum = sum + inum(i, j)
                    
                Next j
                
                '再前进一个走道
                k = k + 1
                Backset(k) = Backset(k - 1) + inp.disty
                i = i + 1
            Loop While Backset(k) < 2 * boundDist
        Else
            main3.outputMsg = main3.outputMsg + "初始扫描线：空间不足以放置一个建筑块"
        End If
    End If
ENDFUNCTEST:
    main3.sum = sum
    main3.far = sum * inp.Area / inputpoly.Area
    main3.sdfar = sum * inp.sdArea / inputpoly.Area
    main3.cr = sum * inp.bsArea / inputpoly.Area

End Function


' module3主程序-绘图
Public Function main3plot(inp As InputInfoMat, inputpoly As QpBlockPointMat, ByVal initialBackset As Double) As OutputCalcs
    Dim boundBox As QpShortCoordinateMat
    Dim scanLine As QpLine
    Dim a As pt, b As pt, cornerPt As pt, c As pt, d As pt
    Dim dx As Double, dy As Double
    Dim tempbool As Boolean
    Dim radAngle As Double  '转轴角度
    
    Dim iDist As Double
    Dim secnum As Integer    '计算过程中的割线数存储
    Dim sum As Integer      '总户数
    
    Dim boundsizex As Double, boundsizey As Double, boundDist As Double   '包围盒大小
    Dim intersec1 As QpIntersec, intersec2 As QpIntersec, intersec3 As QpIntersec   '交点输出
    'Dim line1(2) As Double, line2(2) As Double  '测试用
    
    Dim i As Integer, k As Integer, j As Integer
    Dim dtan As Double, dsin As Double, dcos As Double
    Dim subsize As Double   'size of standard sub-blocks
    
    '初始化
    i = 0: j = 0: k = 0
    sum = 0
    tempbool = False
    dsin = Sin(inp.radAngle)
    dcos = Cos(inp.radAngle)
    dtan = dsin / dcos
    
    
    '获取多边形数据
    'InputPoly = PolyCoord()
    n = inputpoly.numPt

    '获取多边形包围盒
    boundBox = Q_BoundBox(inputpoly)
    boundsizex = boundBox.x(1) - boundBox.x(0)
    boundsizey = boundBox.y(1) - boundBox.y(0)
    boundDist = Sqr(boundsizex * boundsizex + boundsizey * boundsizey)
    
    '获取起算点
    If inp.dirAngle > 0 Then
        cornerPt = findVertexLR(inputpoly, boundBox, initialBackset)
    Else
        cornerPt = findVertexLL(inputpoly, boundBox, initialBackset)
    End If
    
    
    '起算线(东西方向)
    If inp.dirAngle < 45 And inp.dirAngle > -45 Then
        radAngle = inp.dirAngle * 3.14159265 / 180
        scanLine = scanLineEW(cornerPt, radAngle, boundBox.x(0), boundBox.x(1))
        dx = Sin(radAngle): dy = 1 / Cos(radAngle)
        a.x = boundBox.x(0): b.x = boundBox.x(1)
        
        '检查并计算第一条扫描线（初始扫描线）
        i = 0
        Backset(i) = initialBackset
        a.y = scanLine.a.y + Backset(i) * dy: b.y = scanLine.b.y + Backset(i) * dy
        intersec1 = findIntersec(a, b, inputpoly)         '由扫描线找交点，返回交点数据库
        If intersec1.num <= 0 Then
            'Call MsgBox("初始扫描线与地块无交点！", vbOKCancel)
            main3plot.outputMsg = main3plot.outputMsg + "初始扫描线：与地块无交点"
            GoTo ENDFUNCTEST
        Else
            For i = 0 To intersec1.num - 1
                If intersec1.sec(i) > inp.x1 Then tempbool = True
                Next i
        End If
        
        '从南向北扫描，横向联排
        sum = 0: i = 0: j = 0: k = 0
        If tempbool = True Then
            main3plot.outputMsg = main3plot.outputMsg + "检查初始扫描线：成功！"
            Do
                '扫描线1
                a.y = scanLine.a.y + Backset(k) * dy: b.y = scanLine.b.y + Backset(k) * dy
                intersec1 = findIntersec(a, b, inputpoly)         '由扫描线找交点，返回交点数据库
                k = k + 1

                '前进一个进深,扫描线2
                Backset(k) = Backset(k - 1) + inp.y1
                a.y = scanLine.a.y + Backset(k) * dy: b.y = scanLine.b.y + Backset(k) * dy
                intersec2 = findIntersec(a, b, inputpoly)         '由扫描线找交点，返回交点数据库
                
                If intersec2.num <= 0 Then
                    Exit Do
                Else
                    secnum = max(intersec1.num, intersec2.num)
                End If
                For j = 0 To secnum - 1
                    '绘制测试扫描线
                    'line1(0) = intersec1.ptIntersec0(j).x: line1(1) = intersec1.ptIntersec0(j).y: line1(2) = 0
                    'line2(0) = intersec1.ptIntersec1(j).x: line2(1) = intersec1.ptIntersec1(j).y: line2(2) = 0
                    'Call ThisDrawing.ModelSpace.AddLine(line1, line2)
                    'line1(0) = intersec2.ptIntersec0(j).x: line1(1) = intersec2.ptIntersec0(j).y: line1(2) = 0
                    'line2(0) = intersec2.ptIntersec1(j).x: line2(1) = intersec2.ptIntersec1(j).y: line2(2) = 0
                    'Call ThisDrawing.ModelSpace.AddLine(line1, line2)

                    '计算户数
                    '左侧起排点
                    If intersec2.ptIntersec0(j).x < (intersec1.ptIntersec0(j).x - inp.y1 * dsin) Then
                        c.x = intersec1.ptIntersec0(j).x
                        c.y = intersec1.ptIntersec0(j).y
                    Else
                        c.x = intersec2.ptIntersec0(j).x + inp.y1 * dtan * dcos
                        c.y = intersec1.ptIntersec0(j).y + (intersec2.ptIntersec0(j).x - intersec1.ptIntersec0(j).x) * dtan + inp.y1 * dtan * dsin
                    End If
                    
                    '右侧终排点
                    If intersec2.ptIntersec1(j).x > (intersec1.ptIntersec1(j).x - inp.y1 * dsin) Then
                        d.x = intersec1.ptIntersec1(j).x
                        d.y = intersec1.ptIntersec1(j).y
                    Else
                        d.x = intersec2.ptIntersec1(j).x + inp.y1 * dsin
                        d.y = intersec2.ptIntersec1(j).y - inp.y1 * dcos
                    End If
                    
                    '真割线长度
                    iDist = dist(c, d)
                    
                    '标准组团
                    subsize = inp.subnum * inp.x1 + inp.distx
                    main3plot.numxs(i, j) = Int(iDist / subsize)
                    main3plot.rx(i, j) = (iDist - main3plot.numxs(i, j) * subsize + inp.distx)
                    
                    '非标准组团
                    If main3plot.rx(i, j) >= (inp.distx + inp.x1) Then
                        main3plot.numxp(i, j) = Int((main3plot.rx(i, j) - inp.distx) / inp.x1)
                        main3plot.rx(i, j) = iDist - main3plot.numxs(i, j) * subsize - main3plot.numxp(i, j) * inp.x1
                    Else
                        main3plot.numxp(i, j) = 0
                    End If
                    inum(i, j) = main3plot.numxs(i, j) * inp.subnum + main3plot.numxp(i, j)
                    sum = sum + inum(i, j)
                    
                    Call insertUnit(c, main3plot.rx(i, j), main3plot.numxs(i, j), main3plot.numxp(i, j), inp)
                Next j
                
                '再前进一个走道
                k = k + 1
                Backset(k) = Backset(k - 1) + inp.disty
                i = i + 1
            Loop While Backset(k) < 2 * boundDist
        Else
            main3plot.outputMsg = main3plot.outputMsg + "初始扫描线：空间不足以放置一个建筑块"
        End If
    End If
ENDFUNCTEST:
    main3plot.sum = sum
    main3plot.far = sum * inp.Area / inputpoly.Area
    main3plot.sdfar = sum * inp.sdArea / inputpoly.Area
    main3plot.cr = sum * inp.bsArea / inputpoly.Area


End Function
